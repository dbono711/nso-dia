module dia {
  yang-version 1.1;
  namespace "http://dbono711/dia";
  prefix dia;

  import ietf-inet-types { prefix inet; }
  import tailf-common { prefix tailf; }
  import tailf-ncs { prefix ncs; }

  organization
    "Darren Bono";

  contact
    "darren.bono@att.net";

  description
    "NSO service package for Dedicated Internet Access (DIA) services";

  revision 2026-11-04 {
    description "Add customer static routes and CUSTOMER-STATIC prefix-list entries";
  }

  revision 2026-10-28 {
    description "Initial revision";
  }

  grouping interface {
    leaf description {
      tailf:info "Interface description (default: NSO:<customer-name>:<service-id>)";
      type string {
        length "1..240";
      }
    }

    leaf ipv4-address {
      tailf:info "Interface IPv4 address in CIDR notation (e.g., 100.64.16.1/29)";
      type tailf:ipv4-address-and-prefix-length;
      mandatory true;
    }

    leaf port-mode {
      tailf:info "Apply service on port level (true) or on a dot1Q sub-interface (false)";
      type boolean;
      mandatory true;
    }

    leaf vlan-id {
      tailf:info "Service encapsulation VLAN ID, also used as the sub-interface number";
      when "../port-mode = 'false'";
      mandatory true;
      type uint16 {
        range "1 .. 4094";
      }
    }

    container static {
      tailf:info "Customer static routes reachable via this interface";
      presence "true";

      list ipv4-destination-prefix {
        tailf:info "Static route destination prefix";
        key ipv4-prefix;
        min-elements 1;

        leaf ipv4-prefix {
          tailf:info "Destination prefix in CIDR notation (e.g., 100.64.20.0/24)";
          type inet:ipv4-prefix;
        }

        leaf ipv4-forwarding {
          tailf:info "Static route next-hop, must be in the interface subnet (e.g., 100.64.16.2)";
          type inet:ipv4-address;
          mandatory true;
        }

        leaf prefix-list-seq {
          tailf:display-when "false()";
          tailf:info "CUSTOMER-STATIC prefix-list sequence number, allocated in pre-modification";
          type uint32 {
            range "1 .. 4294967294";
          }
        }
      }
    }
  }

  augment /ncs:services {
    list dia {
      tailf:info "Dedicated Internet Access (DIA) Services";
      description "Dedicated Internet Access (DIA) service package";
      key "customer-name service-id";

      uses ncs:service-data;
      ncs:servicepoint dia-servicepoint;

      leaf customer-name {
        tailf:info "Customer name";
        type leafref {
          path "/ncs:customers/ncs:customer/ncs:id";
        }
      }

      leaf service-id {
        tailf:info "Service identifier";
        tailf:cli-allow-range;
        type string;
      }

      container provider-edge {
        tailf:info "Provider Edge (PE) configuration";

        list device {
          tailf:info "Provider Edge device";
          key name;

          leaf name {
            tailf:info "Provider Edge device name";
            type leafref {
              path "/ncs:devices/ncs:device/ncs:name";
            }
            must "contains(/ncs:devices/ncs:device[ncs:name=current()/../name]/ncs:device-type/ncs:cli/ncs:ned-id, 'cisco-ios-cli')" {
              error-message "Provider Edge devices must be Cisco IOS";
            }
          }

          list interface {
            tailf:info "PE customer-facing interface";
            key name;

            leaf name {
              tailf:info "Physical interface name (e.g., Ethernet0/3)";
              tailf:cli-completion-actionpoint dia-interface-name {
                tailf:cli-completion-id "provideredge-";
              }
              type string {
                pattern '(Ethernet|GigabitEthernet|TenGigabitEthernet)[0-9]+(/[0-9]+)*';
              }
            }

            uses interface;
          }
        }
      }
    }
  }
}
